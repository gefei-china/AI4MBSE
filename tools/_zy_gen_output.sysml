"package 'AI需求验证007' {\n    public import '系统架构设计-元模型库（AI生成视图）'::**;\n    package '3 实现域' {\n        package '3.1 软硬件需求';\n        package '3.2 设备结构';\n        package '3.3 追溯分析';\n    }\n    package '2 方案域' {\n        package '2.2 子系统';\n        package '2.3 组件';\n        package '2.1 系统' {\n            package '2.1.3 系统行为分析';\n            package '2.1.2 系统结构定义';\n            package '2.1.4 系统参数分析';\n            package '2.1.5 追溯分析';\n        }\n    }\n    package '1 问题域' {\n        package '1.2 白盒' {\n            package '1.2.1 用户需求' {\n                package 'TMS热管理系统' {\n                    package 'TMS热管理系统_需求' {\n                        public import SI::*;\n                        public import ISQ::*;\n                        private import Requirements::*;\n                        private import ScalarValues::*;\n                        private import Parts::Part;\n                        package 'TMS热管理系统_需求' {\n                            public import SI::*;\n                            public import ISQ::*;\n                            private import Requirements::*;\n                            private import ScalarValues::*;\n                            private import Parts::Part;\n                            doc /* TMS热管理系统利益相关方需求视图（IR层） */\n                            package '关注点定义' {\n                                package '关注点定义' {\n                                    private import Requirements::*;\n                                    doc /* 30条关注点定义 */\n                                }\n                            }\n                            package '利益相关方需求' {\n                                package '利益相关方需求' {\n                                    private import ''利益相关方定义''::*;\n                                    private import Requirements::*;\n                                    package '利益相关方需求' {\n                                        private import ISQ::*;\n                                        private import ''利益相关方定义''::*;\n                                        private import Requirements::*;\n                                        private import ScalarValues::*;\n                                        }\n                                        }\n                                        }\n                                        }\n                                        }\n                                        }\n                                        }\n                                        }\n                                        }\n                                        }\n                                        }\n                                        }\n                                        }\n                                        }\n                                        }\n                                        }\n                                        }\n                                        }\n                                        }\n                                        }\n                                        }\n                                        }\n                                        }\n                                        }\n                                        }\n                                        }\n                                        }\n                                        }\n                                        }\n                                        }\n                                        }\n                                        }\n                                        }\n                                        }\n                                        }\n                                        doc /* 利益相关方需求 - 非功能需求NFR（35条） */\n                                    }\n                                }\n                            }\n                            package '利益相关方定义' {\n                                package '利益相关方定义' {\n                                    private import Parts::Part;\n                                    doc /* 8类利益相关方定义 */\n                                }\n                            }\n                        }\n                    }\n                    package 'TMS热管理系统_视图' {\n                        private import StandardViewDefinitions::*;\n                        private import ''TMS热管理系统_需求''::''利益相关方需求''::*;\n                        private import Views::*;\n                        private import ''TMS热管理系统_需求''::''利益相关方定义''::*;\n                        private import ''TMS热管理系统_需求''::''关注点定义''::*;\n                        package 'TMS热管理系统_视图' {\n                            private import Views::*;\n                            private import ''TMS热管理系统_需求''::*;\n                            doc /* TMS热管理系统利益相关方需求视图（IR层） */\n                        }\n                    }\n                }\n            }\n            package '1.2.6 白盒阶段的追溯分析';\n            package '1.2.2 概念子系统';\n            package '1.2.4 子系统效能';\n            package '1.2.3 功能性分析';\n            package '1.2.5 功能接口分析';\n        }\n        package '1.1 黑盒' {\n            package 'IR004整车IR-4提供舒适的空气湿度' {\n                requirement def 'IR002 整车IR-2 提供空调系统远程控制模式';\n            }\n            package '系统需求SR';\n            package '1.1.2 系统上下文分析';\n            package '1.1.6 追溯分析';\n            package '1.1.4 用例运行场景分析';\n            package '1.1.3 用例分析';\n            package '1.1.5 系统效能';\n        }\n    }\n}\n"
